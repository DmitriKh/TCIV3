TCI-16093-PC5
DEFINITIONS AUTOMATIC TAGS ::=
BEGIN

IMPORTS
RequestWsmTxCount,
RequestWsmRxCount,
RequestWsmTxCountReset,
RequestWsmRxCountReset,
SetInitialState,
SetWsmTxInfo,
StartWsmRx,
StopWsmRx,
StopWsmTx,
StartWsaTxPerdiodic,
StopWsaTxPeriodic,
AddWsaProviderService,
ChangeWsaProviderService,
DelWsaProviderService,
AddUserService,
DelUserService FROM TCI-wsm

GetIPv6InterfaceInfo,
SetIPv6Address,
StartIPv6Ping,
StopIPv6Ping FROM TCI-ip

ATcmdInfo,
ResponseInfo FROM TCI-responseInfo

Indication FROM TCI-indication

ltev2xMtu,
Exception,
Response,
ResultCode,
MsgID FROM TCI-CommonTypes

tciMtu,
RepeatRate,
Opaque,
RadioInterface,
Psid,
RCPI
FROM TCI-CommonTypes
;

TCI16093PC5 ::= CHOICE{
    request         [0] Request,
    response        [1] Response,
    indication      [2] Pc5Indication,
    responseInfo    [3] Pc5ResponseInfo,
    exception       [4] Exception,
    ...
    }

Request ::=  SEQUENCE {
   messageId   MESSAGE-ID-AND-TYPE.&id({MessageTypes}),
   value       MESSAGE-ID-AND-TYPE.&Type({MessageTypes}{@.messageId}),
   ...
   }

MESSAGE-ID-AND-TYPE ::= CLASS {
   &id    MsgID UNIQUE,
   &Type
   } WITH SYNTAX {&Type IDENTIFIED BY &id}

MessageTypes MESSAGE-ID-AND-TYPE ::= {
    { SetInitialState   IDENTIFIED BY setInitialState } |
    { Pc5SetWsmTxInfo IDENTIFIED BY setWsmTxInfo} |
    { StartWsmTx IDENTIFIED BY startWsmTx} |
    { StopWsmTx IDENTIFIED BY stopWsmTx} |
    { Pc5StartWsmRx IDENTIFIED BY startWsmRx} |
    { StopWsmRx IDENTIFIED BY stopWsmRx} |

    { Pc5StartWsaTxPerdiodic IDENTIFIED BY startWsaTxPerdiodic} |
    { StopWsaTxPeriodic IDENTIFIED BY stopWsaTxPeriodic} |
    { AddWsaProviderService IDENTIFIED BY addWsaProviderService} |
    { ChangeWsaProviderService IDENTIFIED BY changeWsaProviderService} |
    { DelWsaProviderService IDENTIFIED BY delWsaProviderService} |
    { Pc5AddUserService IDENTIFIED BY addUserService} |
    { DelUserService IDENTIFIED BY delUserService} |
    { GetIPv6InterfaceInfo IDENTIFIED BY getIpv6InterfaceInfo} |
    { SetIPv6Address IDENTIFIED BY setIpv6Address} |
    { StartIPv6Ping IDENTIFIED BY startIpv6Ping} |
    { StopIPv6Ping IDENTIFIED BY stopIpv6Ping} |

    { SetUeConfig IDENTIFIED BY setUeConfig} |
    { SetFlowConfig IDENTIFIED BY setFlowConfig} |    
    { RequestWsmTxCount IDENTIFIED BY requestWsmTxCount} |
    { RequestWsmRxCount IDENTIFIED BY requestWsmRxCount} |
    { RequestWsmTxCountReset IDENTIFIED BY requestWsmTxCountReset} |
    { RequestWsmRxCountReset IDENTIFIED BY requestWsmRxCountReset} |
    { SendATcommand IDENTIFIED BY sendATcommand} |
    { SendUeConfigXML IDENTIFIED BY sendUeConfigXML } | 
    { StartUdpForwardTx IDENTIFIED BY startUdpForwardTx } |
    { StopUdpForwardTx IDENTIFIED BY stopUdpForwardTx }    
}

setInitialState                         MsgID ::= 1
setWsmTxInfo                            MsgID ::= 2
startWsmTx                              MsgID ::= 3
stopWsmTx                               MsgID ::= 4
startWsaTxPerdiodic                     MsgID ::= 5
stopWsaTxPeriodic                       MsgID ::= 6
startWsmRx                              MsgID ::= 7
stopWsmRx                               MsgID ::= 8
addWsaProviderService                   MsgID ::= 9
changeWsaProviderService                MsgID ::= 10
delWsaProviderService                   MsgID ::= 11
addUserService                          MsgID ::= 12
delUserService                          MsgID ::= 13
getIpv6InterfaceInfo                    MsgID ::= 14
setIpv6Address                          MsgID ::= 15
startIpv6Ping                           MsgID ::= 16
stopIpv6Ping                            MsgID ::= 17

sendUeConfigXML                         MsgID ::= 21
setUeConfig                             MsgID ::= 22
setFlowConfig                           MsgID ::= 23
sendATcommand                           MsgID ::= 24
requestSutStatus                        MsgID ::= 25
requestWsmTxCount                       MsgID ::= 26
requestWsmRxCount                       MsgID ::= 27
requestWsmTxCountReset                  MsgID ::= 28
requestWsmRxCountReset                  MsgID ::= 29
startUdpForwardTx                       MsgID ::= 30
stopUdpForwardTx                        MsgID ::= 31

/* IMPORTED Messages without changes

SetInitialState,
StopWsmRx,
StopWsmTx
RequestWsmTxCount,
RequestWsmRxCount,
RequestWsmTxCountReset,
RequestWsmRxCountReset,
AddWsaProviderService,
ChangeWsaProviderService,
DelWsaProviderService
DelUserService
GetIPv6InterfaceInfo,
SetIPv6Address,
StartIPv6Ping,
StopIPv6Ping
*/

/*
For Wsm transmissions: 
    SetInitialState
    SetUeConfig or SendUeConfigXML
    SetFlowConfig
    Pc5SetWsmTxInfo
    StartWsmTx
    StopWsmTx

For Proxy Mode transmissions (tx only): 
    SetInitialState
    SetUeConfig or SendUeConfigXML
    SetFlowConfig
    StartUdpForwardTx
    StopUdpForwardTx    
*/    

SendATcommand ::=  ATcmdInfo -- e.g. AT+CATM, AT+CCUTLE, AT+CUSPCREQ, AT+CUTCR, AT+CCBRREQ, AT+CV2XDTS, ATV1, ATV0
-- response from SendATcommand is provided via Pc5ResponseInfo

Pc5SetWsmTxInfo ::= SetWsmTxInfo (WITH COMPONENTS {
        psid,
        radio,
        security,
        transmitPowerLevel ABSENT,  -- Not used for LTE-V2X; set Tx Power via SetUeConfig.pMax
        infoElementsIncluded ('000000000000000000000000'B), -- default no WAVE Extension Info elements included
        userPriority ABSENT,        -- Not used for LTE-V2X; set User Priority via SetUeConfig.pppp
        channelIdentifier ABSENT,   -- Not used for LTE-V2X; set Channel via set by SetUeConfig.earfcn
        dataRate ABSENT,            -- Not used for LTE-V2X; set coding rate via set by SetUeConfig.mcs
        timeslot ABSENT,            -- Not used for LTE-V2X
        repeatRate OPTIONAL,        -- this is repeat Rate to be used for actual message transmission which >= than periodicity set via SetFlowConfig
                                    -- repeatRate expressed per 1609.3 and values constrained to support SPS Periodicity
        destinationMACAddr OPTIONAL,-- L2 destination set per 3161/0, 
                                    -- V field and Destination Layer 2 ID to be used in MAC header, 
                                    -- based on the Peer MAC Address from the WSM-WaveShortMessage.request. 
                                    -- Only used in the case of unicast WSM or IP transmission.
        channelLoad ABSENT,         -- Not used for LTE-V2X
        expiryTime  ABSENT,         -- Not used for LTE-V2X
        payload ABSENT              -- Not used for LTE-V2X
    })

StartUdpForwardTx ::= SEQUENCE {   
    udpPort  INTEGER(0..65535),   -- UDP IPv4 port used to forward payload via LTE-V2X radio interface
                                  -- For WSMP, payload must include |Non-IP Type Header|WSMP Packet| see Fig M.6 IEEE 1609.3
                                  -- For IP, payload must include |IP packet| see Fig M.7 IEEE 1609.3                                  
                                  -- IPv4 TOS or IPv6 Traffic Class byte will map to pppp (0-0,1-1...7-7)
    radio    RadioInterface,
    flowId   FlowIdentifier,
    pc5Mtui  INTEGER(0..65535) DEFAULT ltev2xMtu,
    ...
}

StopUdpForwardTx ::= SEQUENCE {
    udpPort  INTEGER(0..65535),
    ...
}

Pc5StartWsaTxPerdiodic ::= StartWsaTxPerdiodic (WITH COMPONENTS {
    radio,
    destinationMACAddr,             -- L2 destination set per 3161/0
    wsaChannelIdentifier ABSENT,    -- set by SetUeConfig.earfcn
    channelAccess ABSENT,
    repeatRate OPTIONAL,            -- repeatRate expressed per 1609.3 and values constrained to support SPS Periodicity, alternatively - SetUeConfig.minTrafficPeriodicity
    ipService,
    security,
    signatureLifetime,
    infoElementIncluded,
    advertiserId OPTIONAL,
    serviceInfos,
    channelinfos,
    wra OPTIONAL,
    -- if the following parameters omitted, use the default values from the SUT MIB
    dataRate ABSENT,                -- set by SetUeConfig.mcs
    userPriority ABSENT,            -- set by SetUeConfig.pppp
    transmitPowerLevel ABSENT,      -- set by SetUeConfig.pMax
    headerExts OPTIONAL
})
-- ??? roadside ? update WSA to match other WSM

SetFlowConfig ::= SEQUENCE(SIZE(0..32)) OF SEQUENCE {
        flowId                  FlowIdentifier,		            -- identifier for the specific flow, selected by a requester
        flowType                ENUMERATED { sps (1), event (2) },
        pppp                    PPPP,                           -- user priority
        serviceId               INTEGER OPTIONAL,               -- used for IPv6 UDP broadcast
        spsReservationSize      SpsReservationSize OPTIONAL,    -- SPS reservation size bytes for the SPS flow creation
        periodicity             TrafficPeriodicity-r14 OPTIONAL,-- reservation periodicity (SPS flow or Event)
        txPower                 P-Max OPTIONAL,
        harq                    BOOLEAN OPTIONAL,               -- Harq On (TRUE) - Off (FALSE)
        txPoolId                INTEGER OPTIONAL,
        -- txProfile also has pool frequency, 
        -- check userPriority ... match dot3
        ...
}

SetUeConfig ::= SEQUENCE {  -- RRC parameters, all optional. Used for those chipset which don't support parameter loading via SendUeConfigXML
    earfcn                  EARFCN OPTIONAL,                -- transmit pool frequency
    pMax                    P-Max OPTIONAL,                 -- Tx power
    bw                      SL-Bandwidth-r12 OPTIONAL,      -- bandwidth
    minMcs                  MCS OPTIONAL,                   -- modulation coding rate - min
    maxMcs                  MCS OPTIONAL,                   -- modulation coding rate - max
    numSubCh                NumSubCh OPTIONAL,              -- number of subchannels
    subChSize               SubChSize OPTIONAL,             -- subchannel size
    pdb                     PDB OPTIONAL,                   -- Packet delay budget i.e. Expiry Time
    ...
}

SendUeConfigXML ::= SEQUENCE {
    counter  INTEGER (1..127),           -- index for the current segment
    total    INTEGER (1..127),           -- total number of segments to be transferred
    crc      Opaque(SIZE(4)) OPTIONAL,   -- CRC32 checksum for the transmitted packet
    pdu      Opaque(SIZE(0..tciMtu)),    -- max Pdu for tci is set in TCI-Common as 1500
    ...
}

StartWsmTx ::= SEQUENCE{  -- handled through WSM-WaveShortMessage.request
    radio           RadioInterface,         -- enumerated radio interfaces (radio0, radio1, ... radio 3)
    psid            Psid,
    flowId          INTEGER,                -- flowID matching one of the SetFlowConfig.flowId
    repeatInterval  RepeatRate,             -- repeatInterval >= reserved flow periodicity via SetFlowConfig.periodicity
                                            -- when set to 0 - one shot message, otherwise periodic with RepeatRate per 1609.3
                                            -- 20ms 50, 100, 200, .. 1000ms, (250, 50, 25, ... 5).
    packetCount     INTEGER (0..65534),     -- 0 - continuous, if > 0 count of messages to be transmitted by DUT
    payload         Opaque(SIZE(0..ltev2xMtu)) OPTIONAL,
    ...
}

Pc5StartWsmRx ::= StartWsmRx (WITH COMPONENTS {
    psid OPTIONAL,
    radio,
	channelIdentifier ABSENT,
    timeSlot ABSENT,
    eventHandling,
    destinationMACAddr OPTIONAL, 
    pduFilter OPTIONAL,
	ssp OPTIONAL
})


Pc5AddUserService ::= AddUserService (WITH COMPONENTS {
    psid,
    radio,
    userRequestType,
    wsaType,
    providerServiceContext OPTIONAL,
    channelIdentifier ABSENT,
    sourceMACAddr ABSENT,
    advertiserId OPTIONAL,
    linkQuality OPTIONAL,
    immediateAccess OPTIONAL,
    wsaChannelIdentifier ABSENT,
    channelAccess ABSENT,
    eventHandling
})
-- should ssp to be included into Pc5AddUserService

/*
   Indication Messages
*/

Pc5Indication ::= Indication (WITH COMPONENTS {
    radio,
    event (
            eWsmPktRx |
            eIpv6PktRx |
            eIcmp6PktRx |
            eIpv6ConfigChanged |
            eDot3RequestMatchedAvailAppService |
            eDot2VerificationCompleteWithResult |
            exception),
    eventParams (WITH COMPONENTS {service} |
                 WITH COMPONENTS {wsm} |
                 WITH COMPONENTS {ip} |
                 WITH COMPONENTS {security}
                 ) OPTIONAL,
    pdu OPTIONAL,
    exception OPTIONAL
    })

/*
   ResponseInfo Messages
*/

Pc5ResponseInfo ::= ResponseInfo (WITH COMPONENTS {
    msgID,
    resultCode,
    info (WITH COMPONENTS {ipv6InterfaceInfo} |
          WITH COMPONENTS {sutInfo} |
          WITH COMPONENTS {atCmdInfo} |
          WITH COMPONENTS {pktCount} |
          WITH COMPONENTS {sutStatus} ) OPTIONAL, -- if exception reported, no InfoContent provided
    exception OPTIONAL
    })

--- PC5 types

FlowIdentifier::= INTEGER (0..65535)
BandwidthPC5  ::= INTEGER (0..255)    --
EARFCN        ::= ARFCN-ValueEUTRA-r9 -- channel number
MCS           ::= INTEGER(0..31)      -- Modulation & Coding scheme
PPPP          ::= SL-Priority-r13
RBSize        ::= ENUMERATED {n6, n15, n25, n50, n75, n100}
RBCount       ::= INTEGER(0..65535)

NumSubCh                    ::= INTEGER
SubChSize                   ::= INTEGER

-- following defintions come from EUTRA-RRC-DEFINITIONS.asn

maxEARFCN2 INTEGER          ::= 262143                      -- Highest value extended EARFCN range
maxSL-TxPool-r12 INTEGER    ::= 4                           -- Maximum number of individual sidelink Tx resource pools

SL-Bandwidth-r12            ::= ENUMERATED {n6, n15, n25, n50, n75, n100}
ARFCN-ValueEUTRA-r9         ::= INTEGER (0..maxEARFCN2)
P-Max                       ::= INTEGER (-30..33)
SL-Priority-r13             ::= INTEGER (1..8)
SL-TxPoolIdentity-r12       ::= INTEGER (1.. maxSL-TxPool-r12)
PDB                         ::= INTEGER (0..1023)
SpsReservationSize          ::= INTEGER (0..ltev2xMtu)
TrafficPeriodicity-r14      ::= ENUMERATED {
    sf20, sf50, sf100, sf200, sf300, sf400, sf500,
    sf600, sf700, sf800, sf900, sf1000}

END
