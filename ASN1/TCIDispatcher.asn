--<OSS.PDU TCI-MsgDispatcher.TCIMessage>--
TCI-Dispatcher
DEFINITIONS AUTOMATIC TAGS ::=
BEGIN

IMPORTS

TCI16093DSRC        FROM TCI-16093-DSRC
TCI16093PC5         FROM TCI-16093-PC5
TCI16094            FROM TCI-16094
TCI80211            FROM TCI-80211
TCI29451            FROM TCI-29451
TCI31611            FROM TCI-31611
TCISutControl       FROM TCI-SutControl
Time64              FROM TCI-CommonTypes
;

TCIMsg ::= SEQUENCE{
    version     INTEGER {currentVersion(3)} (1..127),  -- current protocol version 3
    time        Time64,                                -- UTC time stamp with milliseconds, GPS synchronized
    frame       Frame,                                 -- protocol layer
    ...
    }

Frame ::=CHOICE {
    d16093dsrc [1] TCI16093DSRC,
    --d16092   [2] TCI16092, module is redundant with TCI16093
    d80211     [3] TCI80211,
    d16094     [4] TCI16094,
    d29451     [5] TCI29451,
    sutCtrl    [6] TCISutControl,
    ...,
    d16093PC5  [7] TCI16093PC5,
    d31611     [8] TCI31611
}


END
