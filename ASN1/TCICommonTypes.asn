TCI-CommonTypes
DEFINITIONS AUTOMATIC TAGS ::=
BEGIN

IMPORTS
VarLengthNumber FROM CITSapplMgmtIDs {iso(1) standard(0) cits-applMgmt (17419) ids (1) version1 (1)} -- this is the p-encoded PSID
;

PduData ::= Opaque
PduType ::= ENUMERATED {
    -- d80211frame         (1),     802.11 frame (802.11 header, MAC header) // DEPRECATED. Use d16093payload instead
    -- d16093frame         (2),     WSM frame, including WSM header & payload  // DEPRECATED. Use d16093payload instead
    d16092data          (3),    -- Ieee1609Data including 1609.3 payload
    d16093payload       (4),    -- 1609.3 payload excluding security header/footer
    dIpv6payload        (5)     -- Ipv6 payload
}


dsrcMtu INTEGER ::= 2304
ltev2xMtu INTEGER ::= 8192
ipMtu INTEGER ::= 2304
tciMtu INTEGER ::= 2304  -- to determine how to test cases where TCI mtu is smaller than packet mtu

Opaque ::= OCTET STRING(SIZE(0..65535)) -- mtu_size 1500 for Ethernet
HashedId8  ::= OCTET STRING (SIZE(8))

/*
   Response Messages with simple Result
*/

Response ::= SEQUENCE {
    msgID               MsgID,
    resultCode          ResultCode,
    exception           Exception OPTIONAL,
    ...
}

ResultCode ::= ENUMERATED {
    rcSuccess (0), -- success
    rcFailure (1)  -- failure
}

/*
    Exception Messages
*/
Exception ::= SEQUENCE{
    type        ExceptionType,
    id          ExceptionId OPTIONAL,
    module      Module OPTIONAL,
    description ExceptionText OPTIONAL,
    ...
}

ExceptionType   ::= ENUMERATED{
    info        (0), -- all info messages
    warning     (1), -- all warnings
    error       (2)  -- all errors
}

Module ::= UTF8String (SIZE(0..255))
-- Function/Module reporting an exception

ExceptionId ::= ENUMERATED {
 critical-error (1),
 incorrect-parameter-value (2),
 missing-parameter (3),
 radio-interface-unavailable (4),
 ...    -- future exception IDs
}

ExceptionText ::= UTF8String (SIZE(0..1200))
-- short description of exception

RadioInterface ::= SEQUENCE{
    radio       Radio,
    antenna     Antenna OPTIONAL
}

Radio ::= ENUMERATED {
    radio0 (0),
    radio1 (1),
    radio2 (2),
    radio3 (3)
}

Antenna ::= ENUMERATED {
    antenna1    (1),
    antenna2    (2),
    both        (3)
}

TimeSlot ::= ENUMERATED {    -- consistent with dot3
    alt-slot0       (1),
    alt-slot1       (2),
    continuous      (3)
}

RCPI ::= INTEGER (0..255)
UserPriority ::= INTEGER(0..7)
Time64 ::= INTEGER (0..9223372036854775807)
-- time expressed as the number of milliseconds,
-- due to ASN.1 limitation in OSS, the highest bit is set to 0

Psid ::= VarLengthNumber
--IpAddress ::= UTF8String(SIZE(2..255)) ---- text string containing IPv6 (or IPv4 or hostname). Used as a parameter in WSA, IPv6 configuration, etc
--IpPort ::= INTEGER(0..65535)      ---- UDP port used in WSA, in SetInitialState

--RepeatRate ::= INTEGER (0..255) // Number of messages transmitted per 5sec interval; if set to 0, transmit message one time only
RepeatRate ::= INTEGER ( -- Number of messages transmitted per 5sec interval per dot3; mapping to MinimumTrafficPeriodicity for PC5
    250 |   -- sf20
    100 |   -- sf50
    50  |   -- sf100
    25  |   -- sf200
    16  |   -- sf300
    12  |   -- sf400
    10  |   -- sf500
    8   |   -- sf600
    7   |   -- sf700
    6   |   -- sf800
    5   |   -- sf900, sf1000
    2   |
    1   |
    0)      -- transmit message one time only

MsgID ::=  INTEGER(0..255)

END
