--Purpose: Exercise J2945/1 compliant devices by testing the transmission of all possible BSM configurations,
--         Assist J2945/1 testing by providing easy access to VehicleEventFlags, 
--         Assist J2945/1 testing by toggling required but test-interfering aspects of the IUT (GPS, Congestion Control, BSM Transmission). 
--         This ASN file IS NOT INTENDED to replace in-vehicle testing

--Notes: All value bounds in this document are taken directly from the SAE J2735-2016 standard. Information on the rationale and units of the values can be found in the J2735 standards.

TCI-29451

DEFINITIONS AUTOMATIC TAGS ::= 
BEGIN

IMPORTS
Response, 
Exception, 
Time64,
MsgID FROM TCI-CommonTypes

SetInitialState,
-- SetWsmTxInfo, 
StartWsmTx, 
StopWsmTx,
StartWsmRx, 
StopWsmRx  FROM TCI-wsm

Indication FROM TCI-indication

EnableGpsInput, 
SetLatitude, 
SetLongitude, 
SetElevation, 
SetPositionalAccuracy, 
SetSpeed, 
SetHeading, 
SetAccelerationSet4Way, 
SetGpsTime  FROM TCI-SutControl
;

TCI29451 ::= CHOICE{
    request         [0] Request,
    response        [1] Response,
    indication      [2] D2945Indication,
--  responseInfo    [3] ResponseInfo,
    exception       [4] Exception,
    ...
} 

Request ::=  SEQUENCE {
    messageId   MESSAGE-ID-AND-TYPE.&id({MessageTypes}),
    value       MESSAGE-ID-AND-TYPE.&Type({MessageTypes}{@.messageId}),
    ...
}

MESSAGE-ID-AND-TYPE ::= CLASS {
    &id    MsgID UNIQUE,
    &Type
} WITH SYNTAX {&Type IDENTIFIED BY &id}

MessageTypes MESSAGE-ID-AND-TYPE ::= {
    { SetInitialState IDENTIFIED BY setInitialState} |
    { StartBsmTx IDENTIFIED BY startBsmTx} |
    { StopBsmTx IDENTIFIED BY stopBsmTx} |
    { EnableCongestionMitigation IDENTIFIED BY enableCongestionMitigation} |

    { SetTemporaryID IDENTIFIED BY setTemporaryID} |
    { SetTransmissionState IDENTIFIED BY setTransmissionState} |
    { SetSteeringWheelAngle IDENTIFIED BY setSteeringWheelAngle} |
    { SetBrakeSystemStatus IDENTIFIED BY setBrakeSystemStatus} |
    { SetVehicleSize IDENTIFIED BY setVehicleSize} |
    { SetExteriorLights IDENTIFIED BY setExteriorLights} |
    { SetVehicleEventFlags IDENTIFIED BY setVehicleEventFlags} |
    { StartBsmRx IDENTIFIED BY startBsmRx} |
    { StopBsmRx IDENTIFIED BY stopBsmRx} |

    { EnableGpsInput IDENTIFIED BY enableGpsInput} |
    { SetLatitude IDENTIFIED BY setLatitude} |
    { SetLongitude IDENTIFIED BY setLongitude} |
    { SetElevation IDENTIFIED BY setElevation} |
    { SetPositionalAccuracy IDENTIFIED BY setPositionalAccuracy} |
    { SetSpeed IDENTIFIED BY setSpeed} |
    { SetHeading IDENTIFIED BY setHeading} |
    { SetAccelerationSet4Way IDENTIFIED BY setAccelerationSet4Way} |
    { SetGpsTime IDENTIFIED BY setGpsTime}
}

setInitialState                     MsgID ::= 1
enableGpsInput                      MsgID ::= 2	    -- deprecated, moved to SutControl
startBsmTx                          MsgID ::= 3
stopBsmTx                           MsgID ::= 4
enableCongestionMitigation          MsgID ::= 5

setTemporaryID                      MsgID ::= 6
setLatitude                         MsgID ::= 7	    -- deprecated, moved to SutControl
setLongitude                        MsgID ::= 8	    -- deprecated, moved to SutControl
setElevation                        MsgID ::= 9	    -- deprecated, moved to SutControl
setPositionalAccuracy               MsgID ::= 10	-- deprecated, moved to SutControl
setTransmissionState                MsgID ::= 11
setSpeed                            MsgID ::= 12	-- deprecated, moved to SutControl
setHeading                          MsgID ::= 13	-- deprecated, moved to SutControl
setSteeringWheelAngle               MsgID ::= 14
setAccelerationSet4Way              MsgID ::= 15	-- deprecated, moved to SutControl
setBrakeSystemStatus                MsgID ::= 16
setVehicleSize                      MsgID ::= 17
setExteriorLights                   MsgID ::= 18
setVehicleEventFlags                MsgID ::= 19
startBsmRx                          MsgID ::= 20
stopBsmRx                           MsgID ::= 21
setGpsTime                          MsgID ::= 22	-- deprecated, moved to SutControl


StartBsmTx ::= StartWsmTx (WITH COMPONENTS {
    psid  (WITH COMPONENTS {content (32)}),
    radio,
    repeatRate ABSENT,  -- Assumes BSM repeat rate is set to default 10Hz
    payload ABSENT      -- Assumes BSM payload is generated by the SUT
})

StopBsmTx ::= StopWsmTx (WITH COMPONENTS {
    psid (WITH COMPONENTS {content  (32)})
})

StartBsmRx ::= StartWsmRx (WITH COMPONENTS {
    psid   (WITH COMPONENTS {content    (32)}), -- PSID is optional if eventHandling.rxFlag is set to receive any WSM with PSID
    radio ( WITH COMPONENTS { ..., antenna ABSENT }),
    channelIdentifier (172),        -- default value for BSM
    timeSlot (continuous),          -- default value for BSM
    eventHandling
    })

StopBsmRx ::= StopWsmRx (WITH COMPONENTS {
        psid (WITH COMPONENTS {content  (32)})
    })

EnableCongestionMitigation ::= BOOLEAN
    
SetTemporaryID ::= OCTET STRING (SIZE(4))

SetTransmissionState ::= ENUMERATED {
    neutral         (0),
    park            (1),
    forwardGears    (2),
    reverseGears    (3),
    reserved1       (4),
    reserved2       (5),
    reserved3       (6),   
    unavailable     (7)
}

SetSteeringWheelAngle ::= INTEGER (-126 .. 127)

SetBrakeSystemStatus ::= SEQUENCE {
    brakeAppliedStatus       BIT STRING {
        unavailable (0),
        leftFront   (1),
        leftRear    (2),
        rightFront  (3),
        rightRear   (4)
    },
    tractionControlStatus    ENUMERATED {
        unavailable (0),
        off         (1),
        on          (2),
        engaged     (3)
    },
    antiLockBrakeStatus      ENUMERATED {
        unavailable (0),
        off         (1),
        on          (2),
        engaged     (3)
    },
    stabilityControlStatus   ENUMERATED {
        unavailable (0),
        off         (1),
        on          (2),
        engaged     (3)
    },
    brakeBoostApplied        ENUMERATED {
        unavailable (0),
        off         (1),
        on          (2)
    },
    auxiliaryBrakeStatus     ENUMERATED {
        unavailable (0),
        off         (1),
        on          (2),
        reserved    (3)
    }
}

SetVehicleSize ::= SEQUENCE{
    vehicleWidth     INTEGER(0 .. 1023),
    vehicleLength    INTEGER(0 .. 4095)
}

SetVehicleEventFlags ::= BIT STRING {
    eventHazardLights               (0),
    eventStopLineViolation          (1),
    eventABSactivated               (2),
    eventTractionControlLoss        (3),
    eventStabilityControlActivated  (4),
    eventHazardousMaterials         (5),
    eventReserved1                  (6),
    eventHardBraking                (7),
    eventLightsChanged              (8),
    eventWipersChanged              (9),
    eventFlatTire                   (10),
    eventDisabledVehicle            (11),
    eventAirBagDeployment           (12)
}

SetExteriorLights ::= BIT STRING
{
   lowBeamHeadlightsOn       (0), 
   highBeamHeadlightsOn      (1), 
   leftTurnSignalOn          (2), 
   rightTurnSignalOn         (3), 
   hazardSignalOn            (4), 
   automaticLightControlOn   (5),
   daytimeRunningLightsOn    (6), 
   fogLightOn                (7), 
   parkingLightsOn           (8) 
}


/* 
   Indication Messages
*/

D2945Indication ::= Indication (WITH COMPONENTS {
    radio,
    event ( eWsmPktRx |
        exception),
    eventParams (WITH COMPONENTS {wsm}
                 ) OPTIONAL,
    pdu   OPTIONAL,
    exception OPTIONAL
})

END
